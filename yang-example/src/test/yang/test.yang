module test {
    namespace "http://tail-f.com/ns/example/demo";
    prefix test;
    // yang here
    container employees {
        list employee {
            key "id name";
            leaf id {type uint32;}
            leaf name {type string;}
            leaf age {type uint8;}
            leaf title {type string;}
            leaf city {type string;}
        }
    }
}
