submodule tailf-meta-extensions {

  belongs-to tailf-common {
    prefix tailf;
  }

  organization "Tail-f Systems";

  description
    "This submodule defines Tail-f YANG meta extensions statements.";

  revision 2016-11-24 {
    description
      "Released as part of ConfD-6.3.

       Added tailf:identifier-ref.";
  }

  revision 2013-11-07 {
    description
      "Released as part of ConfD-5.0.

       Added tailf:occurrence.";
  }

  revision 2010-08-19 {
    description
      "Released as part of ConfD-3.3.1.

       Added tailf:snmp-identifier.";
  }

  revision 2010-03-18 {
    description
      "Released as part of ConfD-3.2.";
  }

  /*
   * Types used to describe the extension statements' arguments.
   */

  typedef identifier {
    type string {
      pattern "[A-Za-z_][A-Za-z0-9_-]*";
    }
  }

  typedef identifier-ref {
    type string {
      pattern "([A-Za-z_][A-Za-z0-9_-]*:)?[A-Za-z_][A-Za-z0-9_-]*";
    }
  }

  typedef snmp-identifier {
    type string {
      pattern "[A-Za-z_][A-Za-z0-9_-]*(:[A-Za-z_][A-Za-z0-9_-]*)*";
    }
  }

  typedef tailf-oid {
    type string {
      pattern "(([0-1](\.[1-3]?[0-9]))"
            + "|(2.(0|([1-9]\d*)))"
            + "|([A-Za-z_][A-Za-z0-9_-]*))?"
            + "(\.(0|([1-9]\d*)))+";
    }
  }

  /*
   * Descriptive meta extensions
   */

  extension use-in {
    argument name {
      tailf:arg-type {
        type string;
      }
    }
    tailf:use-in "extension";
    tailf:occurence "*";
    description
      "Specifies in which statements a particular extension statement can be
      used.";
  }

  extension substatement {
    argument name {
      tailf:arg-type {
        type string;
      }
    }
    tailf:use-in "extension";
    tailf:occurence "*";

    tailf:substatement "tailf:occurence";
    description
      "Specifies which statements can occur as substatement to the
      given statement.";
  }

  extension arg-type {
    tailf:use-in "argument";
    tailf:substatement "type" {
      tailf:occurence "1";
    }
    tailf:substatement "default";
    description
      "Specifies the type of the argument.";
  }

  extension occurence {
    argument value {
      tailf:arg-type {
        type enumeration {
          enum "?" {
            description
              "The extenstion may be given zero or one time.
               This is the default.";
          }
          enum "*" {
            description
              "The extenstion may be given zero or multiple times.";
          }
          enum "+" {
            description
              "The extenstion must be given at least once.";
          }
          enum "1" {
            description
              "The extenstion must be given exactly once.";
          }
        }
      }
    }
    tailf:use-in "extension";
    description
      "Specifices how an extension statement may be used.

       If this statement is given as a substatement to 'extension',
       it applies to all 'use-in' statements.

       If this statement is given as a substatement to 'tailf:substatement',
       it applies to this substatement.";
  }

}
