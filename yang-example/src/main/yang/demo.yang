module demo {
    namespace "http://tail-f.com/ns/example/demo";
    prefix demo;
    import ietf-inet-types {
     prefix inet;
    }
      import tailf-common {
        prefix tailf;
      }
    // yang here
    container employees {
        list employee {
            key id;
            leaf id {type uint32;}
            leaf name {type string;}
            leaf age {type uint8;}
            leaf title {type string;}
            leaf city {type string;}
             leaf tt {type error-severity-type ;}
            uses schema-leaf;
           leaf test-option {
             type enumeration {
               enum test-then-set {
                 description
                   "The server will test and then set if no errors.";
               }
               enum set {
                 description
                   "The server will set without a test first.";
               }

               enum test-only {
                 description
                   "The server will only test and not set, even
                    if there are no errors.";
               }
             }
             default "test-then-set";
             description
               "The test option to use.";
           }
        }
    }
      typedef error-severity-type {
        type enumeration {
          enum error {
            description "Error severity";
          }
          enum warning {
            description "Warning severity";
          }
        }
        description "NETCONF Error Severity";
        reference "RFC 6241, Section 4.3";
      }

              typedef subscription-priority {
                type int32;
                description
                  "The numerical priority associated with a subscripition
                   for configuration data changes.";
              }
    grouping schema-leaf {
      description
        "Common schema leaf parameter for modules and submodules.";

      leaf schema {
        type inet:uri;
        description
          "Contains a URL that represents the YANG schema
           resource for this module or submodule.

           This leaf will only be present if there is a URL
           available for retrieval of the schema for this entry.";
      }
    }

      typedef pimAnycastRPSetAnycastAddressType {
        type tailf:hex-list {
          tailf:value-length "4 .. 20";
        }
      }
}
